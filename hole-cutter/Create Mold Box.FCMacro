# -*- coding: utf-8 -*-

import FreeCAD
import FreeCADGui
import Part
import Draft

from FreeCAD import Units

def main():
	selection = FreeCADGui.Selection.getSelection()
	if len(selection) == 0:
		FreeCAD.Console.PrintWarning("Please select an object and then re-run this macro.")
		return

	#model = selection[0]
	#print( "selection is " + model.Label )
	#print( "type is " + model.TypeId)
	#makeMoldBox(model)
	
	for i in range(len(selection)):
		model = selection[i]
		# debugBBound(model)
		# makeMoldBox(model, gutter=0, wall=2, base=18) # mold box cos it didn't fit on Prusa
		makeMoldBox(model, gutter=18, wall=2, base=8) # for shapeways
		model.Visibility = False


	App.activeDocument().recompute()


def makeMoldBox(model, gutter=10, wall=2, base=10, heightOfShape=20):

	# gutter = 10
	# wall = 2
	# base = 10


	# I know heightOfShape cos I made the base 20, but this should be calculated
	# and generally the moldbox height made from the source being any height
	# heightOfShape = 20 

	(scale1, position1) = calculateSizeAndPosition(model, gutter+wall)
	shape1 = Draft.make_clone(model,position1)
	shape1.Label = "outer_shape-" + model.Label
	shape1.Scale = scale1


	(scale2, position2) = calculateSizeAndPosition(model, gutter, wall)
	shape2 = Draft.make_clone(model,position2)
	shape2.Label = "outer_cut-" + model.Label
	shape2.Scale = scale2

	outer = App.activeDocument().addObject("Part::Cut","outer-" + model.Label)
	outer.Base = shape1
	outer.Tool = shape2

	(scale3, position3) = calculateSizeAndPosition(model, 0.0, -base)
	shape3 = Draft.make_clone(model,position3)
	shape3.Label = "inner_shape-" + model.Label
	shape3.Scale = scale3


	outerandinner = App.ActiveDocument.addObject("Part::MultiFuse", "outerandinner-" + model.Label)
	outerandinner.Shapes = [outer,shape3]


	# need a new piece here to remove the base of the inner
	(scale3a, position3) = calculateSizeAndPosition(model, 10.0, -(heightOfShape))
	shape3a = Draft.make_clone(model,position3)
	shape3a.Label = "inner_bottom-" + model.Label
	shape3a.Scale = scale3a

	# cut the bottom away from the inner (so it doesn't go below the outer)
	outerandinnerRemovedBottom = App.activeDocument().addObject("Part::Cut","inner_bottom_cut-" + model.Label)
	outerandinnerRemovedBottom.Base = outerandinner
	outerandinnerRemovedBottom.Tool = shape3a


	(scale4, position4) = calculateSizeAndPosition(model, -wall, -(wall+base))
	shape4 = Draft.make_clone(model,position4)
	shape4.Label = "inner_cut-" + model.Label
	shape4.Scale = scale4


	moldBox = App.activeDocument().addObject("Part::Cut","moldBox-" + model.Label)
	moldBox.Base = outerandinnerRemovedBottom
	moldBox.Tool = shape4
	# place this one where the original was


def calculateSizeAndPosition(model,increase,zoff=0.0):

	bbox = model.Shape.BoundBox

	oXL = bbox.XLength # - bbox.XMin
	oYL = bbox.YLength # - bbox.YMin

	nXL = oXL + increase
	nYL = oYL + increase

	xperc = nXL / oXL
	yperc = nYL / oYL

	scale = App.Vector(xperc, yperc, 1.0)


	bbox = model.Shape.BoundBox
	pos = model.Placement.Base
	halfinc = increase / 2

	cxp = bbox.XMin + (bbox.XLength/2)
	cyp = bbox.YMin + (bbox.YLength/2)

	dx = pos.x - cxp
	dy = pos.y - cyp

	# TODO work out how to scale

	# offset = App.Vector() # how do we calculate this?
	# placement of object vs something on BoundBox ?
	base = model.Placement.Base
	position = App.Vector(base.x + (dx*xperc), base.y + (dy*yperc), base.z+zoff)

	print( model.Label, "calc:", base.x,">",dx,"/",base.y,">",dy )

	return (scale, position)


main()
