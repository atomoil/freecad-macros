# BSplines - https://wiki.freecadweb.org/Draft_BSpline
#  https://forum.freecadweb.org/viewtopic.php?style=4&t=27342
# help( Part.BezierCurve )
# help( Part.BSplineCurve )
# https://forum.freecadweb.org/viewtopic.php?t=41212

import FreeCAD as App
import Draft
from FreeCAD import Placement, Vector, Rotation
from math import cos, sin, pi
from lib import getEmptyLayers, extrudeBase, groupHolesIntoStencil, addBaseHolePart, addCutterPart, addPusherPart

baseHeight = 2
cutterLayers = getEmptyLayers()
holderLayers = getEmptyLayers()
pusherLayers = getEmptyLayers()

def drawLeaf(addTo, xscale=1.0, yscale=1.0):
	print("drawLeaf...")

	doc = App.activeDocument()

	outer = [ 
		App.Vector(0, 0, 0),
		App.Vector(5, 20, 0),
		App.Vector(10, 22, 0),
		App.Vector(30, 20, 0),
		App.Vector(47, 2, 0),
		App.Vector(50, 0, 0),
	]

	for vec in outer:
		vec.scale(xscale, yscale, 1.0)

	(topline, bottomline) = drawLeafOutline(doc, outer, xo=-5, xs=1.4, ys=1.5)
	(newlines,_) = Draft.upgrade([topline, bottomline], delete=True)
	extrudeBase(newlines[0], baseHeight, cutterLayers)
	extrudeBase(newlines[0], baseHeight, pusherLayers)

	(topline, bottomline) = drawLeafOutline(doc, outer, xo=-6.5, xs=1.45, ys=1.55)
	(newlines,_) = Draft.upgrade([topline, bottomline], delete=True)
	extrudeBase(newlines[0], baseHeight, holderLayers)

	(topline, bottomline) = drawLeafOutline(doc, outer, yo=-12)
	createHolesOnSpline(doc, topline, 8, 4, angoff=pi, keepRadius=0.7)
	createHolesOnSpline(doc, bottomline, 8, 4, angoff=pi, keepRadius=0.7)

	(topline, bottomline) = drawLeafOutline(doc, outer, yo=-8, xo=8, xs=0.6, ys=0.65)
	createHolesOnSpline(doc, topline, 5, 3.5, keepRadius=0.7, totalDistance=0.8, startOffset=0.15)
	createHolesOnSpline(doc, bottomline, 5, 3.5, keepRadius=0.7, totalDistance=0.8, startOffset=0.15)

	(topline, bottomline) = drawLeafOutline(doc, outer, yo=-3, xo=12, xs=0.4, ys=0.3)
	createHolesOnSpline(doc, topline, 3, 3, angoff=0, keepRadius=0.8, totalDistance=0.7, startOffset=0.1)
	createHolesOnSpline(doc, bottomline, 3, 3, angoff=0, keepRadius=0.8, totalDistance=0.7, startOffset=0.1)


def drawLeaf2(addTo):
	doc = App.activeDocument()

	outer = [ 
		App.Vector(0, 0, 0),
		App.Vector(15, 35, 0),
		App.Vector(40, 38, 0),
		App.Vector(90, 5, 0),
		App.Vector(100, 0, 0),
	]
	(topline, bottomline) = drawLeafOutline(doc, outer, yo=-12)
	createHolesOnSpline(doc, topline, 12, 4)
	createHolesOnSpline(doc, bottomline, 12, 4)

	(topline, bottomline) = drawLeafOutline(doc, outer, yo=-12, xo=8, xs=0.75, ys=0.7)
	createHolesOnSpline(doc, topline, 9, 3.5, angoff=pi)
	createHolesOnSpline(doc, bottomline, 9, 3.5, angoff=pi)


	(topline, bottomline) = drawLeafOutline(doc, outer, yo=-12, xo=16, xs=0.475, ys=0.4)
	createHolesOnSpline(doc, topline, 6, 3, angoff=pi/2)
	createHolesOnSpline(doc, bottomline, 6, 3, angoff=pi/2)


	# (topline, bottomline) = drawLeafOutline(doc, outer, yo=-8, xo=24, xs=0.4, ys=0.1)
	# createHolesOnSpline(doc, topline, 8, 1.5, angoff=pi)
	# createHolesOnSpline(doc, bottomline, 8, 1.5, angoff=pi)


def drawLeaf1():
	doc = App.activeDocument()

	outer = [ 
		App.Vector(0, 0, 0),
		App.Vector(15, 25, 0),
		App.Vector(25, 28, 0),
		App.Vector(90, 5, 0),
		App.Vector(100, 0, 0),
	]
	(topline, bottomline) = drawLeafOutline(doc, outer, yo=-8)
	createHolesOnSpline(doc, topline, 18, 2.5)
	createHolesOnSpline(doc, bottomline, 18, 2.5)

	(topline, bottomline) = drawLeafOutline(doc, outer, yo=-8, xo=8, xs=0.8, ys=0.7)
	createHolesOnSpline(doc, topline, 14, 2.1, angoff=pi)
	createHolesOnSpline(doc, bottomline, 14, 2.1, angoff=pi)


	(topline, bottomline) = drawLeafOutline(doc, outer, yo=-8, xo=16, xs=0.6, ys=0.4)
	createHolesOnSpline(doc, topline, 10, 1.8)
	createHolesOnSpline(doc, bottomline, 10, 1.8)


	(topline, bottomline) = drawLeafOutline(doc, outer, yo=-8, xo=24, xs=0.4, ys=0.1)
	createHolesOnSpline(doc, topline, 8, 1.5, angoff=pi)
	createHolesOnSpline(doc, bottomline, 8, 1.5, angoff=pi)



def drawLeafOutline(doc,pointsIn,xo=0,yo=0,xs=1,ys=1):
	yo = yo / 2

	points = []
	pointsFlipped = []
	for pt in pointsIn:
		npt = App.Vector((pt.x*xs)+xo, (pt.y*ys)-yo, pt.z)
		fpt = App.Vector(npt.x, (-pt.y*ys)+yo, npt.z)
		points.append( npt )
		pointsFlipped.append( fpt )

	topline = Draft.make_bspline(points, face=False, closed=False, support=None)
	bottomline = Draft.make_bspline(pointsFlipped, face=False, closed=False, support=None)
	doc.recompute()

	return (topline, bottomline)


def addOtherHalfOfShapeToLine(points):

	rev = points[len(points)-2:0:-1]

	# add the array onto itself without the first and last element
	for pt in rev:
		npt = App.Vector(pt.x,-pt.y,pt.z)
		points.append( npt )

	return points
	# print(points);


def createHolesOnSpline(doc, spline, frequency, radius, angoff=0, keepRadius=0.5, totalDistance=1.0, startOffset=0.0):
	kr = radius * keepRadius
	vr = radius * (1-keepRadius)
	print("keep={} var={}".format(kr, vr))
	inc = totalDistance/(frequency-1)
	for i in range(0,frequency):
		val = (i * inc)+startOffset

		# print(i, val)
		# print(spline.Shape.Edges[0])
		loc = spline.Shape.Edges[0].valueAt(val*spline.Shape.Edges[0].Length)
		# print(loc)
		# print("----")
		ang = (i/frequency)*(pi*2)+angoff
		mult = (cos(ang)+1)/2
		radius = kr + (mult * vr)
		dbstr = "ang={:.2f} radius={:.3f} cos={:.3f} cos/2={:.4f}".format(ang, radius, cos(ang), mult)
		print(dbstr)

		lineWidth = 0.45
		addBaseHolePart(doc, loc.x, loc.y, size=radius+0.5, lineWidth=lineWidth, addTo=holderLayers)
		addCutterPart(doc, loc.x, loc.y, size=radius, lineWidth=lineWidth, addTo=cutterLayers, baseHeight=baseHeight)
		addPusherPart(doc, loc.x, loc.y, size=radius, lineWidth=lineWidth, addTo=pusherLayers, baseHeight=baseHeight)
		# circle = doc.addObject("Part::Cylinder","circle-{}".format(i))
		# circle.Radius = '{} mm'.format(radius)
		# circle.Height = '3 mm'
		# placement = Placement(loc,Rotation(Vector(0,0,1),1))
		# circle.Placement = placement


# drawLeaf(cutterLayers)

drawLeaf(cutterLayers, xscale=1.15)
groupHolesIntoStencil(cutterLayers, "leafCutter")
groupHolesIntoStencil(holderLayers, "leafHolder")
groupHolesIntoStencil(pusherLayers, "leafPusher")
