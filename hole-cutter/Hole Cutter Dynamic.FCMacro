# -*- coding: utf-8 -*-

import FreeCAD
import Part
import math

from lib import trig, addCutterPart, addBaseHolePart, createBoxViaSketcher, appendPointsToSketch, groupHolesIntoStencil, createPerpendicularBase, extrudeBase


baseHeight = 1.75


cutterLayers = { 'bases': [], 'inners': [], 'outers': [] }
holderLayers = { 'bases': [], 'inners': [], 'outers': [] }


basePlate = App.ActiveDocument.addObject("Part::Box","HolderBase")
basePlate.Label = "Base Plate"
basePlate.Height = str(baseHeight) + ' mm'
basePlate.Length = '100 mm'
basePlate.Width = '100 mm'
holderLayers['bases'].append(basePlate)



def createGridOfHoles(mx, my, holeSize, gridSize):

	basePlate = App.ActiveDocument.addObject("Part::Box","HolderBase")
	basePlate.Label = "Base Plate"
	basePlate.Height = str(baseHeight) + ' mm'
	cutterLayers['bases'].append(basePlate)

	# gridSize = holeSize
	# holeSize = 4
	# mx = 10
	# my = 10
	for x in range(mx):
		for y in range(my):
			nx = gridSize + (x*gridSize*2)
			ny = gridSize + (y*gridSize*2)
			size = (((math.sin(x+(y/2))+1)/2) * (holeSize*0.5)) + (holeSize*0.5)
			addCutterPart(App.activeDocument(), nx, ny, size, 0.25, cutterLayers)
			addBaseHolePart(App.activeDocument(), nx, ny, size, 0.25, holderLayers)

	basePlate.Length = str(mx*gridSize*2)
	basePlate.Width = str(my*gridSize*2)



def createCircleOfHoles():
	ox = 50
	oy = 50
	distance = 10
	total = 30
	angle = 360/(total/3)
	for i in range(0,total):
		distance = 10 + (i * 1.1)
		(x, y) = trig(ox,oy,angle*i,distance)
		addCutterPart(App.activeDocument(), x, y, 3+(0.2*i), 0.25, cutterLayers)


def createLineOfHoles(ox,oy,angle,distance,total):
	margin = 2
	holeSize = (distance/total)/2 - margin
	for i in range(0,total):
		thisDistance = i * (distance/(total-1))
		thisHoleSize = (holeSize*0.6) + ((holeSize*0.4)*(i/total))
		(x,y) = trig(ox,oy,angle,thisDistance)
		addCutterPart(App.activeDocument(), x,y,thisHoleSize,0.25,cutterLayers)
		addBaseHolePart(App.activeDocument(), x,y,thisHoleSize, 0.25, holderLayers)

	createBoxViaSketcher(ox,oy,angle,distance,holeSize*0.6,holeSize, cutterLayers)


def createBoxViaSketcher(x,y,angle,distance,nearRadius,farRadius,addTo):

	sketch = App.activeDocument().addObject('Sketcher::SketchObject', 'BaseSketch')

	nearL = trig(x,y,angle-90,nearRadius)
	nearR = trig(x,y,angle+90,nearRadius)
	(farX, farY) = trig(x,y,angle,distance)
	farL = trig(farX,farY,angle-90,farRadius)
	farR = trig(farX,farY,angle+90,farRadius)

	points = [nearL, farL, farR, nearR]
	
	appendPointsToSketch(sketch, points)

	extrudeBase(sketch, baseHeight, addTo)

	# extrude.DirMode = "Normal"
	# extrude.DirLink = None
	# extrude.LengthFwd = 10.000000000000000
	# extrude.LengthRev = 0.000000000000000
	# 
	# extrude.Reversed = False
	# extrude.Symmetric = False
	# extrude.TaperAngle = 0.000000000000000
	# extrude.TaperAngleRev = 0.000000000000000


def createFan():
	cx = 10
	cy = 95
	distanceInner = 200
	distanceMiddle = 175
	distanceOuter = 150

	createLineOfHoles(cx,cy+60,-12,distanceOuter,12)
	createLineOfHoles(cx+5,cy+50,-10.3,distanceOuter-5,8)
	createLineOfHoles(cx,cy+40,-8,distanceMiddle,14)
	createLineOfHoles(cx+5,cy+30,-6.25,distanceMiddle-5,10)
	createLineOfHoles(cx,cy+20,-4,distanceInner,16)
	createLineOfHoles(cx+7,cy+10,-2.5,distanceInner-7,10)
	createLineOfHoles(cx,cy,0, distanceInner,13)
	createLineOfHoles(cx+7,cy-10,2.5,distanceInner-7,10)
	createLineOfHoles(cx,cy-20,4,distanceInner,16)
	createLineOfHoles(cx+5,cy-30,6.25,distanceMiddle-5,10)
	createLineOfHoles(cx,cy-40,8,distanceMiddle,14)
	createLineOfHoles(cx+5,cy-50,10.3,distanceOuter-5,8)
	createLineOfHoles(cx,cy-60,12,distanceOuter,12)

	createPerpendicularBase(cx,cy-60,8,120,cutterLayers)
	createPerpendicularBase(cx+(distanceOuter/2)-8,cy-80,8,160,cutterLayers)

	createPerpendicularBase(cx+distanceOuter-8,cy-90,8,180,cutterLayers) # TODO: calculate the position of far end
	createPerpendicularBase(cx+distanceMiddle-8,cy-65,8,130,cutterLayers)
	createPerpendicularBase(cx+distanceInner-8,cy-35,8,70,cutterLayers)



# createGridOfHoles(5,5,4,5)
# createGridOfHoles(6,5,4,5)
# createCircleOfHoles()
# createBoxViaSketcher()
# createLineOfHoles(0,0,0,100,5)
# createLineOfHoles(0,40,5,120,8)
createFan()
groupHolesIntoStencil(cutterLayers, "Stencil")
groupHolesIntoStencil(holderLayers, "Holder")
